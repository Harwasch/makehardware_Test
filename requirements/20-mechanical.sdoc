[DOCUMENT]
TITLE: Mechanical Requirements
UID: DOC-MECHANICAL

[GRAMMAR]
IMPORT_FROM_FILE: hardware.sgra

[TEXT]
STATEMENT: >>>
Mechanical requirements. Each one Refines a ``SYS-`` requirement.

``MEC-001`` carries 120 W of the 300 W allowed by ``SYS-004``. It is written
against the coupling-quality product k times Q rather than against a coil
technology, so the choice between an etched and a wound conductor is settled on
a measurement rather than a preference.
<<<

[REQUIREMENT]
UID: MEC-001
TITLE: Coil pair loss and coupling quality
STATEMENT: >>>
The coil pair shall dissipate no more than 120 W at 3.0 kW transferred, which
requires a coupling-quality product k times Q of at least 49 measured at 85 kHz
at the maximum gap of ``SYS-006``.
<<<
RATIONALE: >>>
Coil-to-coil efficiency in a compensated inductive link is governed by the
product of coupling and quality factor, not by resistance alone. 120 W of 3.0 kW
is 96.0% coil-to-coil, and inverting the standard expression gives k times Q of
49. Analysis in ``docs/design/coil-model.md`` computes the worst-case coupling
across the whole ``SYS-006`` envelope as 0.705 in air, not the 0.5 first
assumed from the electric-vehicle literature - that literature works at a
gap-to-diameter ratio of 0.3 to 0.5, where this dock sits at 0.067. At k of
0.705 the required quality factor is 69, not the 98 the earlier assumption
implied.

An etched coil MEETS this requirement, but only as a TRANSPOSED multi-track
winding - a plain parallel-layer stack does not. On the house's 102 by 203 mm
rectangle, 24 turns of 0.25 mm trace in 4 oz copper with 16 transposed layers
reaches k times Q of 75.0 at the WORST corner of the ``SYS-006`` envelope,
against the 49 required. Twelve layers reaches 61.1. The same geometry as a
plain parallel stack reaches 45.2, and fails.

The reason is that parallel layers do not reduce resistance as 1 over N.
Proximity resistance depends on conductor volume and on B squared and NOT on the
current a conductor carries, so parallel layers - which do not change total
ampere-turns - add proximity loss in proportion to N while reducing transport
loss as 1 over N. Measured: two identical PCB layers in parallel at 100 kHz cut
resistance by 15.9 percent, not 50. Transposing the stack, so every layer spends
equal time at every depth, is the published fix, and even a quarter-transposed
stack passes.

This requirement is deliberately written against k times Q and dissipation
rather than against a conductor technology, so the choice is settled by
arithmetic. See ``docs/design/adr-0001-coil-technology.md``.
<<<
VERIFICATION: Test
BUDGET: 120 W
STATUS: Draft
RELATIONS:
- TYPE: Parent
  VALUE: SYS-004
  ROLE: Refines

[REQUIREMENT]
UID: MEC-002
TITLE: Coil assembly inductance
STATEMENT: >>>
Each coil assembly, with its ferrite backing in place and at the nominal gap,
shall have a self-inductance within 5% of the value the compensation network is
tuned for, and the two assemblies shall match each other within 2%.
<<<
RATIONALE: >>>
For a 3.0 kW transfer at resonance with a 400 V bus on both ends, the mutual
inductance must be about 81 microhenries. On the house's 102 by 203 mm
rectangle the coupling is 0.461 at the nominal 20 mm gap, so the coil is about
180 microhenries at 32 turns - fifteen times the v1 coil's 12 microhenries. The
rectangle couples less well than a 300 mm circular pair (0.705) because a 20 mm
gap is 20 percent of its short dimension rather than 7 percent of a diameter.
The v1 coil is not merely small, it puts the link in a regime where holding
3.0 kW requires running far off resonance, which directly defeats the resonance
tracking the firmware exists to perform. The 2% matching limit exists because
the resonant gain of the link collapses when the two tanks are tuned apart.
See ``docs/design/v1-baseline.md`` finding F8.
<<<
VERIFICATION: Test
STATUS: Draft
RELATIONS:
- TYPE: Parent
  VALUE: SYS-001
  ROLE: Refines

[REQUIREMENT]
UID: MEC-003
TITLE: Coupling coefficient over the docking envelope
STATEMENT: >>>
The coupling coefficient shall be at least 0.40 everywhere within the gap and
misalignment envelope of ``SYS-006``, measured with both ferrite backings and
both cold plates fitted.
<<<
RATIONALE: >>>
0.40 is retained as the floor. On the house's 102 by 203 mm rectangle, across
the tightened ``SYS-006`` envelope, the coupling computes to 0.645 at the 10 mm
nominal gap with 5 mm of offset and 0.558 at the 14 mm limit - a margin of 1.40
at the worst point, against the 1.09 the earlier 20 mm free-docking envelope
would have left. The decision to charge on deck in a locating bracket is what
bought that back.

The floor stays at 0.40 rather than being raised to the computed figure, because
ferrite raises coupling but a conductive cold plate lowers it through induced
eddy currents, and neither is modelled. The 1.40 margin is what absorbs that. Measuring with the backings and plates
fitted matters because both change the field pattern substantially; a coupling
figure taken on bare coils is not the figure the system will run at. No
coupling coefficient appears anywhere in the v1 source material.
<<<
VERIFICATION: Test
STATUS: Draft
RELATIONS:
- TYPE: Parent
  VALUE: SYS-006
  ROLE: Refines

[REQUIREMENT]
UID: MEC-004
TITLE: Coil pad thermal path
STATEMENT: >>>
Each coil pad shall conduct up to 60 W into its mounting structure with the coil
conductor staying below 100 degC in the maximum specified ambient, with no
pumped coolant and no forced air.
<<<
RATIONALE: >>>
60 W is half the ``MEC-001`` allowance, one pad each. 100 degC keeps a
polyimide-insulated conductor and a potting compound well inside their ratings
and keeps the copper resistance rise, which is about 30% from 20 degC to
100 degC, inside what the loss budget already assumes. The ambient is an open
question from the vision interview and this requirement cannot be closed until
it is answered.
<<<
VERIFICATION: Simulation
STATUS: Draft
RELATIONS:
- TYPE: Parent
  VALUE: SYS-007
  ROLE: Refines

[REQUIREMENT]
UID: MEC-008
TITLE: Enclosure thermal path at the design ambient
STATEMENT: >>>
Every enclosure shall conduct its full dissipation into the vessel or vehicle
structure with no internal component exceeding its rated maximum junction or
surface temperature at the +55 degC ambient of ``SYS-016``, with no pumped
coolant and no forced air.
<<<
RATIONALE: >>>
This is the requirement that turns the environmental envelope into a design
constraint. At +55 degC ambient and a 100 degC conductor limit the whole chain -
conductor to ferrite to interface to cold plate to structure - has 45 degC to
work in, and the structure itself is not at ambient because it is also in the
sun. An open-deck enclosure gains heat from solar load as well as losing it to
air, so the enclosure's external finish is a thermal design parameter and not a
cosmetic one.
<<<
VERIFICATION: Simulation
STATUS: Draft
RELATIONS:
- TYPE: Parent
  VALUE: SYS-016
  ROLE: Refines

[REQUIREMENT]
UID: MEC-005
TITLE: Coil assembly immersion sealing
STATEMENT: >>>
Each coil assembly shall be sealed such that full immersion in seawater produces
no conductive path to the coil conductor and no change in self-inductance beyond
2%.
<<<
RATIONALE: >>>
``SYS-005`` requires the link to survive immersion. The inductance clause is the
one that is easy to miss: seawater in the winding cavity changes the effective
permittivity around the conductor and detunes the tank, which the resonance
tracker would then chase into a regime the compensation network is not designed
for.
<<<
VERIFICATION: Test
STATUS: Draft
RELATIONS:
- TYPE: Parent
  VALUE: SYS-005
  ROLE: Refines

[REQUIREMENT]
UID: MEC-006
TITLE: Mechanical parts producible without programme-specific tooling
STATEMENT: >>>
Every mechanical part other than the coil conductor shall be producible by
3-axis machining, sheet fabrication or an off-the-shelf moulding, with no part
requiring a tool made for this programme alone.
<<<
RATIONALE: >>>
Carries the ``SYS-011`` intent into the mechanical parts. The coil conductor is
excluded because ``MEC-001`` may not be satisfiable within it; every other part,
including the ferrite backing and the cold plate, should stay inside it.
<<<
VERIFICATION: Inspection
STATUS: Draft
RELATIONS:
- TYPE: Parent
  VALUE: SYS-011
  ROLE: Refines

[REQUIREMENT]
UID: MEC-007
TITLE: Magnetic and material property traceability
STATEMENT: >>>
Every magnetic material, potting compound and thermal interface material shall
have its relevant properties recorded in ``docs/reference/manifest.yaml`` against
a datasheet revision or a measurement made in this programme.
<<<
RATIONALE: >>>
The mechanical half of ``SYS-010``. Ferrite permeability and loss at 85 kHz, and
thermal interface conductivity, are exactly the numbers that get taken from
memory and are exactly the ones the thermal and magnetic designs rest on. The v1
white paper names ferrite backing without naming a material at all.
<<<
VERIFICATION: Inspection
STATUS: Draft
RELATIONS:
- TYPE: Parent
  VALUE: SYS-010
  ROLE: Refines

[REQUIREMENT]
UID: MEC-009
TITLE: Interface requirement - the mounting structure is the heat sink
STATEMENT: >>>
The structure each pad mounts to - the deck fixture, the vehicle mounting and
the test packaging alike - shall conduct the full pad dissipation of ``MEC-004``
into free air with at least 12 times the pad footprint in external surface area,
and shall hold the coil conductor below 100 degC in the ``SYS-016`` ambient with
no pumped coolant and no forced air. This programme shall state this as a
numbered interface requirement to whoever builds that structure, and shall meet
it in the test packaging.
<<<
RATIONALE: >>>
This requirement exists because the pad cannot cool itself and the arithmetic is
not close. A flat plate in still air sheds roughly 150 W per square metre at an
acceptable temperature rise, so the 207 square centimetre pad sheds about 3.1 W
from its own faces. The design has to remove about 36 W. The pad face is
therefore irrelevant to the thermal problem and every watt leaves through the
bracket, which needs roughly 2400 square centimetres of external surface - about
twelve times the pad footprint.

A finned aluminium plate of about 400 by 500 mm provides that comfortably, which
is exactly why the decision to charge on deck in a fixture is what makes an
etched coil viable at all. A hull-mounted pad with only its own faces to work
with could not have been cooled by any coil technology.

The fixture became the mechanical team's on 2026-08-31 (``VIS-013``). This
requirement was NOT withdrawn with it, and the distinction is the whole point:
we no longer design the bracket, but the coil we do design is only viable
because something cools it, so the surface area becomes a number we levy on the
integrator rather than a number we satisfy ourselves. Handing over a coil
without handing over its heat sink requirement is how a design that closed on
paper arrives at a 90 degC pad. The test packaging must meet it too, because a
thermal measurement taken on a rig with a smaller heat sink would understate the
temperature the delivered system runs at.

The 12 times figure is researched but NOT independently verified - the
verification pass on the thermal topic did not run - so it must be confirmed
against a second source before this requirement is closed. The concrete warning
behind it is measured: a published fully transposed multi-track PCB coil at
3.3 kW reached 90.3 degC and was still rising when power was cut at 33 minutes.
See ``docs/design/adr-0001-coil-technology.md``.
<<<
VERIFICATION: Simulation
STATUS: Draft
RELATIONS:
- TYPE: Parent
  VALUE: SYS-007
  ROLE: Refines

[REQUIREMENT]
UID: MEC-010
TITLE: Test packaging construction and pin locating
STATEMENT: >>>
The test packaging shall locate each coil assembly on two dowel pins in a
hole-and-slot pattern, shall set the gap of ``SYS-017`` with shims or a
graduated adjuster readable to 0.5 mm, and shall be producible by 3-axis
machining and sheet fabrication from stock material with no programme-specific
tooling.
<<<
RATIONALE: >>>
Hole-and-slot on two pins is the standard way to fix a plate in six degrees of
freedom without over-constraining it: the round hole fixes position, the slot
fixes rotation and leaves the pin-spacing tolerance and thermal growth somewhere
to go. Locating on two round holes instead is the common mistake - it fights the
pin spacing and either binds or has to be opened up until it no longer locates.

Shims set the gap rather than a screw thread because a shim stack is directly
measurable with the same gauge that verifies it, and ``SYS-017`` needs the gap
KNOWN to 0.5 mm rather than merely adjustable.

The producibility clause mirrors ``MEC-006``. It is here rather than inherited
because the test packaging is test equipment and would otherwise sit outside
that requirement's scope, and a rig that needs its own tooling does not get
built in time to verify anything.
<<<
VERIFICATION: Inspection
STATUS: Draft
RELATIONS:
- TYPE: Parent
  VALUE: SYS-017
  ROLE: Refines
